[DOCUMENT]
TITLE: CTA – úložiště

[[SECTION]]
TITLE: Databáze

[REQUIREMENT]
UID: CTA-DB-001
TITLE: Databáze se vytvoří a udržuje v aktuálním schématu
STATEMENT: Při otevření se chybějící databáze vytvoří a chybějící migrace se aplikují. Verze schématu je uložená v PRAGMA user_version a opakované otevření ji nemění.

[REQUIREMENT]
UID: CTA-DB-002
TITLE: Cizí klíče se kontrolují vždy
STATEMENT: Každé spojení otevřené nástrojem má zapnuté foreign_keys, takže zápis porušující cizí klíč selže.

[REQUIREMENT]
UID: CTA-DB-003
TITLE: Databáze používá WAL
STATEMENT: Databáze běží v režimu journal_mode = WAL.

[REQUIREMENT]
UID: CTA-DB-004
TITLE: Novější databáze se neotevře
STATEMENT: Databázi se schématem novějším, než nástroj zná, nástroj odmítne otevřít a nic v ní nezmění.

[REQUIREMENT]
UID: CTA-DB-005
TITLE: Zavřené spojení uvolní soubor
STATEMENT: Po zavření spojení nástroj nedrží databázový soubor otevřený, takže ho lze přesunout nebo smazat i na Windows.

[REQUIREMENT]
UID: CTA-DB-006
TITLE: Migrace zachová data
STATEMENT: Databáze ze starší verze se při otevření převede na aktuální schéma a všechna dosavadní data zůstanou zachovaná.

[[/SECTION]]

[[SECTION]]
TITLE: Import

[REQUIREMENT]
UID: CTA-IMPORT-001
TITLE: Import uloží run a nic neukládá dvakrát
STATEMENT: Import uloží run včetně informace, zda běžel nad necommitnutými změnami, zdrojové reporty a výsledky. Stejný test a stejná chyba jsou v databázi napříč runy jen jednou.

[REQUIREMENT]
UID: CTA-IMPORT-002
TITLE: Import je idempotentní
STATEMENT: Druhý import runu se stejným otiskem nezmění počet řádků a ohlásí, že run už je importovaný.

[REQUIREMENT]
UID: CTA-IMPORT-003
TITLE: Import je atomický
STATEMENT: Když import selže, v databázi po něm nezůstanou žádná data.

[REQUIREMENT]
UID: CTA-IMPORT-004
TITLE: Import je šetrný
STATEMENT: Import 10 000 výsledků trvá nejvýše 2 s a alokuje nejvýše 50 MB. Špička živé paměti při 100 000 výsledcích není víc než 2× vyšší než při 10 000.

[[/SECTION]]

[[SECTION]]
TITLE: Identita runu

[REQUIREMENT]
UID: CTA-ID-001
TITLE: Otisk runu je stabilní
STATEMENT: Fingerprint je SHA-256 ze seřazených SHA-256 všech zdrojových reportů. Nezávisí na pořadí reportů a jeho formát se nemění, jinak by se stejné reporty importovaly znovu. Report se hashuje proudově.

[REQUIREMENT]
UID: CTA-ID-002
TITLE: Klíč runu určuje jeho původ
STATEMENT: RunKey má tvar local/<počítač>/<čas UTC> pro lokální běh a ci/<workflow run id>/<attempt>/<job> pro běh v CI.

[[/SECTION]]

[[SECTION]]
TITLE: Stejné jméno testu v jednom runu

[REQUIREMENT]
UID: CTA-IMPORT-005
TITLE: Stejná jména se sloučí a pád se neschová
STATEMENT: Výsledky se stejným plným jménem v jednom runu se uloží jako jeden řádek. Uloží se počet výskytů a součet doby běhu a vyhraje horší výsledek bez ohledu na pořadí. Součet výskytů odpovídá počtu výsledků v reportu.

[[/SECTION]]
