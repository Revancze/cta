[DOCUMENT]
TITLE: CTA – parsery

[[SECTION]]
TITLE: TRX

[REQUIREMENT]
UID: CTA-PARSE-001
TITLE: TRX se přečte úplně
STATEMENT: Parser přečte z TRX všechny výsledky včetně celého jména testu, výsledku, doby běhu, chyby, důvodu přeskočení a výstupu, a to z reportů xUnit i NUnit.

[REQUIREMENT]
UID: CTA-PARSE-002
TITLE: Neúplný report se odmítne
STATEMENT: Report s jiným počtem výsledků, než sám uvádí, bez čítačů, s neznámým výsledkem nebo jiného formátu parser odmítne. Odmítne i report bez výsledků z běhu, který skončil chybou. Nejistota se nikdy nezmění v úspěch.

[REQUIREMENT]
UID: CTA-PARSE-003
TITLE: Otisk chyby seskupuje stejná selhání
STATEMENT: Otisk tvoří typ výjimky, zpráva bez čísel, GUIDů a cest a první rámec stack trace. Stack trace neznámého formátu otisk nerozbije.

[REQUIREMENT]
UID: CTA-PARSE-004
TITLE: Parser čte proudově
STATEMENT: Špička živé paměti nezávisí na velikosti výstupů testů a při 100 000 výsledcích nepřekročí 32 MB. V paměti zůstávají jen identifikátory testů a sdílené názvy tříd.

[[/SECTION]]

[[SECTION]]
TITLE: JUnit XML

[REQUIREMENT]
UID: CTA-PARSE-005
TITLE: JUnit XML se přečte úplně
STATEMENT: Parser přečte JUnit XML z pytestu, CTestu a JunitXml.TestLoggeru včetně celého jména testu, výsledku, doby běhu, chyby, důvodu přeskočení a výstupu. Vypnutý test se nikdy nevydává za úspěšný. Čas startu se převezme, jen když report uvádí časovou zónu.

[REQUIREMENT]
UID: CTA-PARSE-006
TITLE: Neúplný JUnit report se odmítne
STATEMENT: Report s jiným kořenem, s počtem testů, který nesedí s atributem tests, se sadou bez atributu tests, s počtem selhání, chyb, přeskočených nebo vypnutých testů, který nesedí s tím, co report uvádí, s neplatným počtem nebo neplatnou dobou běhu parser odmítne. Počet, který nástroj neuvádí, se nekontroluje.

[[/SECTION]]

[[SECTION]]
TITLE: Detekce formátu

[REQUIREMENT]
UID: CTA-PARSE-007
TITLE: Formát se pozná podle obsahu
STATEMENT: Formát reportu (TRX, JUnit XML, NUnit 3 XML, xUnit v2 XML) se pozná podle kořenového elementu a jeho jmenného prostoru, nikdy podle názvu souboru. Čte se jen začátek souboru. Neznámý formát, prázdný soubor nebo soubor, který není XML, se odmítne.

[[/SECTION]]

[[SECTION]]
TITLE: NUnit 3 XML

[REQUIREMENT]
UID: CTA-PARSE-008
TITLE: NUnit 3 XML se přečte úplně
STATEMENT: Parser přečte NUnit 3 XML z nunit3-console i z NunitXml.TestLoggeru včetně celého jména testu, sestavení, výsledku, doby běhu, chyby, důvodu a výstupu. Selhání s označením Error, Invalid nebo Cancelled je Error, Inconclusive se neztrácí a Warning je Passed se zachovaným důvodem.

[REQUIREMENT]
UID: CTA-PARSE-009
TITLE: Neúplný NUnit report se odmítne
STATEMENT: Report s jiným kořenem, bez celkového počtu, s počtem testů nebo výsledků, který nesedí s tím, co report uvádí, s neznámým výsledkem nebo neplatnou dobou běhu parser odmítne. Počet, který nástroj neuvádí, se nekontroluje.

[[/SECTION]]

[[SECTION]]
TITLE: Detail výsledku

[REQUIREMENT]
UID: CTA-PARSE-010
TITLE: Detail výsledku se neztratí
STATEMENT: Co report uvádí nad rámec šesti stavů (například Timeout, Warning, xfail, Setup), se uloží do OutcomeDetail, jen pokud to report říká v pevné podobě. Na detailu nezávisí verdikt. U sloučených výsledků patří detail k výsledku, který vyhrál.

[[/SECTION]]
